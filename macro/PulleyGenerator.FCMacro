import FreeCAD as App
import Part

doc = App.newDocument("Pulley")

# Parameters
outer_diameter = 8.0
width = 4.0
shaft_diameter = 5.0
groove_radius = 0.60
groove_depth = groove_radius / 1.5

outer_radius = outer_diameter / 2
shaft_radius = shaft_diameter / 2

# Base cylinder
pulley = Part.makeCylinder(outer_radius, width)

# Shaft bore
shaft = Part.makeCylinder(shaft_radius, width)
pulley = pulley.cut(shaft)

# Groove with torus
major_radius = outer_radius - groove_depth + groove_radius
torus = Part.makeTorus(major_radius, groove_radius)
torus.translate(App.Vector(0, 0, width / 2))

pulley = pulley.cut(torus)

Part.show(pulley)
doc.recompute()
